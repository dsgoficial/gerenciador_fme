FME workspace valida_angulos_edif_1517214596047.fmw

Parameters:
- db_SourceDataset_POSTGIS_2 = treinamento_conv_rs_1   # Database
- utgeom_postgis_sql_where_clause = st_intersects(geom,st_geomfromewkt('SRID=31982;MULTIPOLYGON(((262789.72853 7066743.2657,262797.52998 7066840.98285,262824.24727 7066935.29983,262868.85345 7067022.59126,262929.63393 7067099.50185,263004.25245 7067163.07529,263089.8408 7067210.86796,263183.10915 7067241.04279,263280.47245 7067252.43992,267435.01793 7067328.6501,271588.64849 7067403.49351,275743.23369 7067477.0039,275840.94276 7067469.12205,275935.2362 7067442.3278,276022.48968 7067397.65102,276099.34947 7067336.80894,276162.86132 7067262.14014,276210.58404 7067176.51464,276240.68333 7067083.2236,276252.00227 7066985.85283,276333.00616 7062368.68475,276414.10876 7057752.61472,276495.34944 7053135.40095,276487.46158 7053037.71269,276460.66932 7052943.43974,276416.00205 7052856.20414,276355.17591 7052779.35757,276280.52791 7052715.85253,276194.92608 7052668.12894,276101.65931 7052638.02039,276004.311 7052626.68366,271854.48575 7052552.93641,267705.69611 7052477.85331,263555.74915 7052401.39457,263458.05277 7052409.20178,263363.75621 7052435.91682,263276.48255 7052480.51325,263199.58502 7052541.27759,263136.01819 7052615.87513,263088.22444 7052701.43967,263058.0401 7052794.68366,263046.62492 7052892.02444,262960.86109 7057509.48976,262875.24265 7062125.83162,262789.72853 7066743.2657)))'))
- priv_LOG_FILE =   # Log File
- priv_DestDataset_POSTGIS = $(db_SourceDataset_POSTGIS_2)   # Database

Readers:
- POSTGIS_1: POSTGIS from $(db_SourceDataset_POSTGIS_2)

Writers:
- POSTGIS_2: POSTGIS to $(priv_DestDataset_POSTGIS)

edgv.constr_edificacao_a (reader POSTGIS_1)
    attributes: id serial, nome varchar(80), tipo int2, situacao_fisica int2, material_construcao int2, observacao text, tipo_comprovacao int2, tipo_insumo int2, data_modificacao timestamp, controle_id uuid, ultimo_usuario varchar(255)
    -> Deaggregator_3
Deaggregator_3
    GEOM_NAME_FIELD = _geometry_name
    ID_ATTR = _hierarchy_id
    PART_NUMBER_FIELD = _part_number
    ID_SELECTION = ID and Parent ID
    MODE = Flatten One Level
    LIST_ATTR_MODE_LOOKUP = LEAN
    CHILD_ID_ATTR = _hierarchy_child_id_list
    COPY_ATTR = Every Node
    SPLIT_COMPOSITES = No
    EXPLODE_INSTANCES = No
    PARENT_ID_ATTR = _hierarchy_parent_id
    DEAGGREGATED -> CircularityCalculator
CircularityCalculator
    CALC_GEOM = CONVEX_HULL
    CIRC_ATTR = _circularity
    -> Tester_4
Tester_4
    TEST_DESCRIPTION = ""
    TEST_CLAUSE = TEST @Value(_circularity) < 0.99
    BOOL_OP = OR
    TEST_MODE = Automatic
    PASSED -> PythonCaller
PythonCaller
    PYTHONSOURCE:
      import fme
      import fmeobjects
      import math
      import numpy as np

      class FeatureProcessor(object):
          def __init__(self):
              pass

          def calcAngle(self, p1, p2, p3):
              a = np.array([p1[0],p1[1]])
              b = np.array([p2[0],p2[1]])
              c = np.array([p3[0],p3[1]])
              ba = a - b
              bc = c - b
              denominator = (np.linalg.norm(ba) * np.linalg.norm(bc))
              if denominator > 0:
                  cosine_angle = np.dot(ba, bc) / denominator
                  if cosine_angle > -1 and cosine_angle < 1:
                      angle = np.arccos(cosine_angle)
                      return round(abs(math.degrees(angle)))%90
                  else:
                      return 0
              else:
                  return 0

          def createFeature(self,coords,angle,coordsys):
              newFeature = fmeobjects.FMEFeature()
              point = fmeobjects.FMEPoint()
              point.setX(coords[0])
              point.setY(coords[1])
              newFeature.setGeometry(point)
              newFeature.setAttribute('angle', angle)
              newFeature.setCoordSys(coordsys)
              return newFeature

          def input(self,feature):
              coords = feature.getAllCoordinates()
              for i in range(1,len(coords)-1):
                  angle = self.calcAngle(coords[i-1],coords[i],coords[i+1])
                  if angle > 5 and angle < 85:
                      self.pyoutput(self.createFeature(coords[i],angle,feature.getCoordSys()))
          def close(self):
              pass
    PYTHONSYMBOL = FeatureProcessor
    -> AttributeCreator
AttributeCreator
    ATTR_LIST = obs,Ângulo diferente de 90 graus, verificar se coerente. Corrigir se for o caso.
    -> Bufferer
Bufferer
    CAP_STYLE = Round
    INTERP_SEGMENTS = 8
    OFFSET = 3
    BUFFERED -> Counter
Counter
    START = 0
    CNT_ATTR = _count
    DOMAIN = counter
    SCOPE = Global
    -> Aggregator
Aggregator
    GROUP_BY = _count
    SEP = ,
    ACCUM_ATTRS_NAME = Yes
    AGGREGATE_TYPE = Homogeneous Collection (If Possible)
    MODE = Geometry - Assemble One Level
    ORDERED = No
    AGGREGATE -> edgv.aux_valida_a (writer POSTGIS_2)
edgv.aux_valida_a (writer POSTGIS_2)
    attributes: id serial,PRIKEY, obs text, data_modificacao timestamp, controle_id uuid, ultimo_usuario varchar(255)
